module example {
  namespace "http://example.com/example";
  prefix example;

  import ietf-inet-types {
    prefix inet;
  }

  // container other {
  //   leaf name {
  //     type string;
  //     default "HELLO";
  //   }
  // }

  container interface {
    leaf name {
      type string;
    }

    leaf subinterface {
      type string;
    }

    leaf shutdown {
      type boolean;
      default false;
    }

    leaf ipv4-address {
      type inet:ipv4-address;
      description "IPv4 address of the interface";
    }

    leaf mtu {
      type uint16;
    }

    container access-list {
      presence true;

      list rule {
        key endpoint;

        leaf endpoint {
          type inet:ipv4-address;
        }

        leaf action {
          type enumeration {
            enum ALLOW;
            enum DENY;
            enum DEFAULT;
          }
          default DEFAULT;
        }
      }
    }

    list neighbour {
      key "address vrf interface";

      leaf address {
        type inet:ipv4-address;
      }

      leaf vrf {
        type string;
      }

      leaf interface {
        type string;
      }

      leaf state {
        type enumeration {
          enum UP;
          enum DOWN;
        }
        default DOWN;
      }

      leaf information {
        type string;
      }

      container names {
        presence true;

        list name {
          key "id";

          leaf id {
            type uint16;
          }

          leaf name {
            type string;
          }
        }
      }
    }

  }
}
